module lsi-ivi-load {
  yang-version 1.1;
  namespace "urn:lsi:params:xml:ns:yang:ivi-load";
  prefix load;

  organization  "Lightside Instruments AS";

  description
    "Load management module designed
     after the IVI Load Class which does not exist.";

  revision 2024-09-30 {
    description
      "Initial.";
  }

  feature measurement;

  
  container load {
    list channel {
      key "name";
      leaf name {
        type string;
      }
      leaf resistance {
        mandatory true;
        description
          "Specifies the resistance of the load.";
        units "Ohm";
        type decimal64 {
          fraction-digits 9;
        }
      }
      leaf transient-resistance {
        mandatory false;
        description
          "Specifies the transient resistance of the load.";
        units "Ohm";
        type decimal64 {
          fraction-digits 9;
        }
      }
      leaf transient-frequency {
        mandatory false;
        description
          "Specifies the frequency of transient operations.";
        units "Hz";
        type decimal64 {
          fraction-digits 2;
        }
      }
    }
  }

  container load-state {
    config false;
    list channel {
      key "name";
      leaf name {
        type string;
      }
      container measurement {
        if-feature "measurement";
        leaf voltage {
          units "Volt";
          type decimal64 {
            fraction-digits 9;
          }
        }
        leaf current {
          units "Ampere";
          type decimal64 {
            fraction-digits 9;
          }
        }
      }
    }
  }
}
